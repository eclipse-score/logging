/********************************************************************************
 * Copyright (c) 2025 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package MwLog

import ScoreReq

ScoreReq.AoU CircularAllocatorPoolSizing {
    description = '''The integrator shall size the local memory pool of mw::log's circular allocators (via the
    application-specific logging configuration) to cover the application's maximum concurrent log message
    volume, so that mw::log never needs to fall back to global heap allocation after the initialization phase.'''
    safety = ScoreReq.Asil.B
    version = 1
}
