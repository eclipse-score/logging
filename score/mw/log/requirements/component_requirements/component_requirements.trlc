/********************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package MwLog

import MwLogFeature
import ScoreReq

// Source: https://github.com/eclipse-score/logging/blob/main/docs/components/mw_log/requirements/requirements.rst
// Copy kept until tooling is set up; helps to avoid drifts until then.

// comp_req__log__avoid_signal_processing
ScoreReq.CompReq AvoidSignalProcessing {
    description = '''The component shall not register any signal handler.'''
    safety = ScoreReq.Asil.B
    derived_from = [MwLogFeature.FEAT_ErrorHandling@1, MwLogFeature.AsilLevelSupport@1]
    version = 1
}

// comp_req__log__file_descriptor_flags
ScoreReq.CompReq FileDescriptorFlags {
    description = '''The component shall set the FD_CLOEXEC (or O_CLOEXEC) flag on all the file descriptors
    it owns.'''
    safety = ScoreReq.Asil.B
    derived_from = [MwLogFeature.SecurityLogAccess@1]
    version = 1
}

// comp_req__log__dlt_verbose_mode
ScoreReq.CompReq DltVerboseMode {
    description = '''mw::log shall implement DLT verbose mode. Generation of messages shall be done in
    DLT-conform format, allowing messages to be sent by Datarouter without additional reprocessing.'''
    safety = ScoreReq.Asil.QM
    derived_from = [MwLogFeature.CompatibilityDltProtocol@1]
    version = 1
}

// comp_req__log__autosar_log_trace_spec
ScoreReq.CompReq AutosarLogTraceSpec {
    description = '''mw::log shall implement "Specification of Log and Trace for Adaptive Platform". Release
    of specification used shall be in agreement with the rest of Adaptive AUTOSAR stack.'''
    safety = ScoreReq.Asil.QM
    derived_from = [MwLogFeature.CompatibilityDltProtocol@1, MwLogFeature.SeverityLevels@1]
    version = 1
}

// comp_req__log__inactive_logstream
ScoreReq.CompReq InactiveLogStreamBehavior {
    description = '''mw::log library shall not perform any useful activity if log level of LogStream object is
    insufficient for given context. LogStream object shall not generate serialized messages if the severity of
    the message does not allow it to be sent.'''
    safety = ScoreReq.Asil.QM
    derived_from = [MwLogFeature.FilteringLogLevels@1, MwLogFeature.ResourceConsumptionPerformance@1]
    version = 1
}

// comp_req__log__shm_file_permissions
ScoreReq.CompReq SharedMemoryFilePermissions {
    description = '''Logging shared-memory files shall have read-only posix file permission for group and
    others. The shared-memory file created by mw::log shall be read-only for group and others.'''
    safety = ScoreReq.Asil.B
    derived_from = [MwLogFeature.SecurityLogAccess@1, MwLogFeature.ConfigPermissions@1]
    version = 1
}

// comp_req__log__forward_to_system_logger
ScoreReq.CompReq ForwardToSystemLogger {
    description = '''The system logger backend shall forward the logs to the native system logger mechanism.
    Under QNX, slogger2 shall be used.'''
    safety = ScoreReq.Asil.QM
    derived_from = [MwLogFeature.EarlyStartupLogging@1]
    version = 1
}

// comp_req__log__system_backend_activation
ScoreReq.CompReq SystemBackendActivation {
    description = '''The system logger backend shall be enabled if and only if the log mode contains
    "kSystem".'''
    safety = ScoreReq.Asil.QM
    derived_from = [MwLogFeature.ConfigOnDemand@1]
    version = 1
}

// comp_req__log__local_allocation_strategy
ScoreReq.CompReq LocalAllocationStrategy {
    description = '''mw::log shall use local allocators to avoid using global heap. Global heap allocation
    (if any) shall be limited to the initialization phase of application lifecycle.'''
    safety = ScoreReq.Asil.B
    derived_from = [MwLogFeature.ResourceConsumptionRuntime@1, MwLogFeature.AsilLevelSupport@1]
    version = 1
}

// comp_req__log__no_endless_loops
ScoreReq.CompReq BoundedLoopExecution {
    description = '''mw::log shall not contain unbound loops or loops with unchecked exit conditions.'''
    safety = ScoreReq.Asil.B
    derived_from = [MwLogFeature.AsilLevelSupport@1, MwLogFeature.ResourceConsumptionRuntime@1]
    version = 1
}

// comp_req__log__avoid_locks
ScoreReq.CompReq TimeBoundedLocking {
    description = '''mw::log shall be free of time-unbound locks and shall implement strategies to limit wait
    time. Time limit shall be defined based on requirements from functions on individual ECU. Mutual
    exclusion mechanisms shall include priority inversion protection.'''
    safety = ScoreReq.Asil.B
    derived_from = [MwLogFeature.AsilLevelSupport@1, MwLogFeature.ResourceConsumptionPerformance@1]
    version = 1
}

// comp_req__log__cross_locking
ScoreReq.CompReq CrossLockingPrevention {
    description = '''Cross-application and cross-thread dependencies shall be avoided. A thread logging in a
    loop shall not block other thread's execution.'''
    safety = ScoreReq.Asil.B
    derived_from = [MwLogFeature.AsilLevelSupport@1, MwLogFeature.ResourceConsumptionRuntime@1]
    version = 1
}

// comp_req__log__index_size_checking
ScoreReq.CompReq IndexAndSizeChecking {
    description = '''Indices in data structures and sizes of data accessed or copied shall be checked for
    plausibility to avoid high runtime utilization through long iterations or data corruption.'''
    safety = ScoreReq.Asil.B
    derived_from = [MwLogFeature.AsilLevelSupport@1]
    version = 1
}

// comp_req__log__memory_bound_checking
ScoreReq.CompReq MemoryBoundChecking {
    description = '''Memory boundaries shall be explicitly checked when writing to shared memory.'''
    safety = ScoreReq.Asil.B
    derived_from = [MwLogFeature.AsilLevelSupport@1]
    version = 1
}
