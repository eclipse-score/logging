/********************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package MwLogBackend

import ScoreReq

ScoreReq.ControlMeasure BoundedSharedMemoryAccess {
    description = "Shared-memory writer/reader implementations shall explicitly check indices and buffer bounds before every read from or write to shared memory."
    safety = ScoreReq.Asil.B
    mitigates = "MwLogBackend.LogMessageLossOrCorruption"
    version = 1
    note = "PLACEHOLDER entry -- not a completed FMEA."
}
